--**MOD+***********************************************************************
--* Module:    ARUBAWIRED-NETWORKING-OID.mib
--*
--* (c) Copyright 2017-2021 Hewlett Packard Enterprise Development LP
--* All Rights Reserved.
--*
--* The contents of this software are proprietary and confidential
--* to the Hewlett-Packard Development Company, L.P.  No part of this
--* program may be photocopied, reproduced, or translated into another
--* programming language without prior written consent of the
--* Hewlett-Packard Development Company, L.P.
--*
--* Purpose: This file contains MIB definition of ARUBAWIRED-NETWORKING-OID
--*
--**MOD-***********************************************************************

ARUBAWIRED-NETWORKING-OID DEFINITIONS ::= BEGIN

IMPORTS
        enterprises, MODULE-IDENTITY, OBJECT-IDENTITY
            FROM SNMPv2-SMI;

hpeNetworking MODULE-IDENTITY
         LAST-UPDATED "202011200000Z"  -- Nov 20, 2020

         ORGANIZATION "HPE/Aruba Networking Division"
         CONTACT-INFO "Hewlett Packard Company
                       8000 Foothills Blvd.
                       Roseville, CA 95747"

         DESCRIPTION  "This MIB module defines HPE Networking
                       product hardware MIBs and proprietary MIBs. "

         REVISION     "202011200000Z"  -- Nov 20, 2020
         DESCRIPTION  "Added PORTVLAN MIB module."

         REVISION     "202011030000Z"  -- Nov 03, 2020
         DESCRIPTION  "Updated with 4100i PSU  OID information."

         REVISION     "202009210000Z"  -- Sep 21, 2020
         DESCRIPTION  "Updated with 6100 PSU  OID information."

         REVISION     "202008140000Z"  -- August 14, 2020
         DESCRIPTION  "Updated with fixed 8360 OID information."

         REVISION     "202006120000Z"  -- June 12, 2020
         DESCRIPTION  "Updated with fixed PSU OID information."

         REVISION     "202004130000Z"  -- Apr 13, 2020
         DESCRIPTION  "Updated with JL762A new Product OID information."

         REVISION     "202003170000Z"  -- Mar 17, 2020
         DESCRIPTION  "Added 8360 Product SKUs OID information."

         REVISION     "202001300000Z"  -- Jan 30, 2020
         DESCRIPTION  "Updated with JL687A new Product OID information."

         REVISION     "202001140000Z"  -- Jan 14, 2020
         DESCRIPTION  "Updated with 6200 switch information."

         REVISION     "202001060000Z"  -- Jan 06, 2020
         DESCRIPTION  "Updated with 6400 switch information."

         REVISION     "201911210000Z"  -- Nov 21, 2019
         DESCRIPTION  "Updated with 6100 switch information."

         REVISION     "201909260000Z"  -- Sep 26, 2019
         DESCRIPTION  "Updated with 6200 switch information."

         REVISION     "201908260000Z"  -- Aug 26, 2019
         DESCRIPTION  "Updated with 6400 switch information."

         REVISION     "201905140000Z"  -- May 14, 2019
         DESCRIPTION  "Updated with 6400 switch information."

         REVISION     "201904160000Z"  -- Apr 16, 2019
         DESCRIPTION  "Updated port vendor types."

         REVISION     "201904150000Z"  -- Apr 15, 2019
         DESCRIPTION  "Added LLDP MIB module."

         REVISION     "201812190000Z"  -- Dec 19, 2018
         DESCRIPTION  "Updated with 6300 switch information."

         REVISION     "201810100000Z"  -- Oct 10, 2018
         DESCRIPTION  "Added new 8325 switches and updated description
                       text for all 8325 switches"

         REVISION     "201804120000Z"  -- Apr 12, 2018
         DESCRIPTION  "Made changes to move VSX MIB under new OID tree."

         REVISION     "201804090000Z"  -- Apr 09, 2018
         DESCRIPTION  "Added new 8320 switches and updated description
                       text for all 8320 switches"

         REVISION     "201711280000Z"  -- Nov 28, 2017
         DESCRIPTION  "Added port vendor types"

         REVISION     "201711140000Z"  -- Nov 14, 2017
         DESCRIPTION  "Added RPM and Power sensors"

         REVISION     "201711020000Z"  -- Nov 2, 2017
         DESCRIPTION  "Added 8400 Rear Display Module"

         REVISION     "201710240000Z"  -- Oct 24, 2017
         DESCRIPTION  "Updated Aruba Wired MIB Object Names with a
                       standard convention"

         REVISION     "201708300000Z"  -- Aug 30, 2017
         DESCRIPTION  "Updated with 8320 switch information"

         REVISION     "201704110000Z"  -- Apr 11, 2017
         DESCRIPTION  "Updated with 8400 SKU information"

         ::= { hpe 4 }

hpe    OBJECT IDENTIFIER ::= { enterprises  47196 }

-- definition of HPENetworking Objects
-- reserving object with zero
reservedhpeNetworking OBJECT IDENTIFIER ::=  { hpeNetworking 0 }

-- grouping all wired devices under a separate group
wiredNetworkingDevices OBJECT IDENTIFIER ::= { hpeNetworking 1 }

-- categorization of MIB portions
arubaOS-CX OBJECT IDENTIFIER ::= { wiredNetworkingDevices 1 }

wndDeviceIds OBJECT IDENTIFIER ::= { arubaOS-CX 1 }

wndComponentIds OBJECT IDENTIFIER ::= { arubaOS-CX 2 }

wndFeatures OBJECT IDENTIFIER ::= { arubaOS-CX 3 }

-- detailing of products

arubaWiredSwitchJL375A OBJECT-IDENTITY
        STATUS      current
        DESCRIPTION "The authoritative identifier for the
                     JL375A Aruba 8400 8-slot chassis switch."
        ::= { wndDeviceIds 1 }

arubaWiredSwitchJL479A OBJECT-IDENTITY
        STATUS      current
        DESCRIPTION "The authoritative identifier for the
                     JL479A Aruba 8320 48p 10G SFP/SFP+ and 6p 40G QSFP+ chassis switch."
        ::= { wndDeviceIds 2 }

arubaWiredSwitchJL579A OBJECT-IDENTITY
        STATUS      current
        DESCRIPTION "The authoritative identifier for the
                     JL579A Aruba 8320 32p QSFP+ chassis switch."
        ::= { wndDeviceIds 3 }

arubaWiredSwitchJL581A OBJECT-IDENTITY
        STATUS      current
        DESCRIPTION "The authoritative identifier for the
                     JL581A Aruba 8320 48p 1G/10GBASE-T and 6p 40G QSFP+ chassis switch."
        ::= { wndDeviceIds 5 }

arubaWiredSwitchJL635A OBJECT-IDENTITY
        STATUS      current
        DESCRIPTION "The authoritative identifier for the
                     JL635A Aruba 8325 8325-48Y8C chassis switch."
        ::= { wndDeviceIds 50 }

arubaWiredSwitchJL636A OBJECT-IDENTITY
        STATUS      current
        DESCRIPTION "The authoritative identifier for the
                     JL636A Aruba 8325 8325-32C chassis switch."
        ::= { wndDeviceIds 70 }

arubaWiredSwitchJL658A OBJECT-IDENTITY
        STATUS      current
        DESCRIPTION "The authoritative identifier for the
                     Aruba 6300M 24SFP+/4SFP56 Swch."
        ::= { wndDeviceIds 100 }

arubaWiredSwitchJL659A OBJECT-IDENTITY
        STATUS      current
        DESCRIPTION "The authoritative identifier for the
                     Aruba 6300M 48SR PoE CLS6 /4SFP56 Swch."
        ::= { wndDeviceIds 101 }

arubaWiredSwitchJL660A OBJECT-IDENTITY
        STATUS      current
        DESCRIPTION "The authoritative identifier for the
                     Aruba 6300M 24SR PoECLS 6 /4SFP56 Swch."
       ::= { wndDeviceIds 102 }

arubaWiredSwitchJL661A OBJECT-IDENTITY
        STATUS      current
        DESCRIPTION "The authoritative identifier for the
                     Aruba 6300M 48G PoE CLS 4 /4SFP56 Swch."
       ::= { wndDeviceIds 103 }

arubaWiredSwitchJL662A OBJECT-IDENTITY
        STATUS      current
        DESCRIPTION "The authoritative identifier for the
                     Aruba 6300M 24G PoE CLS 4 /4SFP56 Swch."
       ::= { wndDeviceIds 104 }

arubaWiredSwitchJL663A OBJECT-IDENTITY
        STATUS      current
        DESCRIPTION "The authoritative identifier for the
                     Aruba 6300M 248G /4SFP56 Swch."
       ::= { wndDeviceIds 105 }

arubaWiredSwitchJL664A OBJECT-IDENTITY
        STATUS      current
        DESCRIPTION "The authoritative identifier for the
                     Aruba 6300M 24G /4SFP56 Swch."
       ::= { wndDeviceIds 106 }

arubaWiredSwitchJL665A OBJECT-IDENTITY
        STATUS      current
        DESCRIPTION "The authoritative identifier for the
                     Aruba 6300F 48G PoE CLS 4 /4SFP56 Swch."
       ::= { wndDeviceIds 107 }

arubaWiredSwitchJL666A OBJECT-IDENTITY
        STATUS      current
        DESCRIPTION "The authoritative identifier for the
                     Aruba 6300F 48G PoE CLS 4 /4SFP56 Swch."
       ::= { wndDeviceIds 108 }

arubaWiredSwitchJL667A OBJECT-IDENTITY
        STATUS      current
        DESCRIPTION "The authoritative identifier for the
                     Aruba 6300F 48G /4SFP56 Swch."
       ::= { wndDeviceIds 109 }

arubaWiredSwitchJL668A OBJECT-IDENTITY
        STATUS      current
        DESCRIPTION "The authoritative identifier for the
                     Aruba 6300F 24G /4SFP56 Swch."
       ::= { wndDeviceIds 110 }

arubaWiredSwitchJL762A OBJECT-IDENTITY
        STATUS      current
        DESCRIPTION "The authoritative identifier for the
                     Aruba 6300M 48G /4SFP56 Pwr2Prt Swch."
       ::= { wndDeviceIds 111 }

arubaWiredSwitchR0X24A OBJECT-IDENTITY
        STATUS      current
        DESCRIPTION "The authoritative identifier for the
                     Aruba 6405 Chassis."
        ::= { wndDeviceIds 150 }

arubaWiredSwitchR0X25A OBJECT-IDENTITY
        STATUS      current
        DESCRIPTION "The authoritative identifier for the
                     Aruba 6410 Chassis."
        ::= { wndDeviceIds 151 }

arubaWiredSwitchJL675A OBJECT-IDENTITY
        STATUS      current
        DESCRIPTION "The authoritative identifier for the
                     Aruba 6100 48G CLS4 4SFP+ 370W."
       ::= { wndDeviceIds 250 }

arubaWiredSwitchJL676A OBJECT-IDENTITY
        STATUS      current
        DESCRIPTION "The authoritative identifier for the
                     Aruba 6100 48G 4SFP+."
       ::= { wndDeviceIds 251 }

arubaWiredSwitchJL677A OBJECT-IDENTITY
        STATUS      current
        DESCRIPTION "The authoritative identifier for the
                     Aruba 6100 24G CLS4 4SFP+ 370W."
       ::= { wndDeviceIds 252 }

arubaWiredSwitchJL678A OBJECT-IDENTITY
        STATUS      current
        DESCRIPTION "The authoritative identifier for the
                     Aruba 6100 24G 4SFP+."
       ::= { wndDeviceIds 253 }

arubaWiredSwitchJL679A OBJECT-IDENTITY
        STATUS      current
        DESCRIPTION "The authoritative identifier for the
                     Aruba 6100 12G CLS4 2G/2SFP+ 139W."
       ::= { wndDeviceIds 254 }

arubaWiredSwitchJL724A OBJECT-IDENTITY
        STATUS      current
        DESCRIPTION "The authoritative identifier for the
                     Aruba 6200F 24G 4SFP+ Swch."
       ::= { wndDeviceIds 300 }

arubaWiredSwitchJL725A OBJECT-IDENTITY
        STATUS      current
        DESCRIPTION "The authoritative identifier for the
                     Aruba 6200F 24G CL4 4SFP+370W Swch."
       ::= { wndDeviceIds 301 }

arubaWiredSwitchJL726A OBJECT-IDENTITY
        STATUS      current
        DESCRIPTION "The authoritative identifier for the
                     Aruba 6200F 48G 4SFP+ Swch."
       ::= { wndDeviceIds 302 }

arubaWiredSwitchJL727A OBJECT-IDENTITY
        STATUS      current
        DESCRIPTION "The authoritative identifier for the
                     Aruba 6200F 48G CL4 4SFP+370W Swch."
       ::= { wndDeviceIds 303 }

arubaWiredSwitchJL728A OBJECT-IDENTITY
        STATUS      current
        DESCRIPTION "The authoritative identifier for the
                     Aruba 6200F 48G CL4 4SFP+740W Swch."
       ::= { wndDeviceIds 304 }

arubaWiredSwitchJL717A OBJECT-IDENTITY
        STATUS      current
        DESCRIPTION "The authoritative identifier for the Aruba 8360
        32p 1/10/25G SFP/SFP+/SFP28 and 4p 40/100G QSFP+/QSFP28 switch."
       ::= { wndDeviceIds 400 }

arubaWiredSwitchJL718A OBJECT-IDENTITY
        STATUS      current
        DESCRIPTION "The authoritative identifier for the Aruba 8360
        16p 1/10/25G SFP/SFP+/SFP28 and 2p 40/100G QSFP+/QSFP28 switch."
       ::= { wndDeviceIds 401 }

arubaWiredSwitchJL719A OBJECT-IDENTITY
        STATUS      current
        DESCRIPTION "The authoritative identifier for the Aruba 8360
        48p 1/10/25G SFP/SFP+/SFP28 and 6p 40/100G QSFP+/QSFP28 switch."
        ::= { wndDeviceIds 402 }

arubaWiredSwitchJL720A OBJECT-IDENTITY
        STATUS      current
        DESCRIPTION "The authoritative identifier for the Aruba 8360
        48p 10GBASE-T and 4p 40/100G QSFP+/QSFP28 switch."
       ::= { wndDeviceIds 403 }

arubaWiredSwitchJL721A OBJECT-IDENTITY
        STATUS      current
        DESCRIPTION "The authoritative identifier for the Aruba 8360
        12p 40/100G QSFP+/QSFP28 switch."
       ::= { wndDeviceIds 404 }

arubaWiredSwitchJL722A OBJECT-IDENTITY
        STATUS      current
        DESCRIPTION "The authoritative identifier for the Aruba 8360
        24p 10G SFP/SFP+ and 2p 40/100G QSFP+/QSFP28 switch."
       ::= { wndDeviceIds 405 }

-- sensors are sub type of parts

wndSensors  OBJECT IDENTIFIER ::= { wndComponentIds 1 }

arubaWiredTemperatureSensor OBJECT-IDENTITY
        STATUS      current
        DESCRIPTION "Identifier for a temperature sensor type."
        ::= { wndSensors 1 }

arubaWiredRPMSensor OBJECT-IDENTITY
        STATUS      current
        DESCRIPTION "Identifier for a fan RPM sensor type."
        ::= { wndSensors 2 }

arubaWiredPowerSensor OBJECT-IDENTITY
        STATUS      current
        DESCRIPTION "Identifier for a PSU power sensor type."
        ::= { wndSensors 3 }

-- slots are sub-type of parts

wndSlots  OBJECT IDENTIFIER ::= { wndComponentIds 2 }

arubaWiredSwitch8400FanTraySlot OBJECT-IDENTITY
        STATUS      current
        DESCRIPTION "Represents slot for Aruba X731 Fan Tray. "
        ::= { wndSlots 1 }

arubaWiredSwitch8400PowerSupplySlot OBJECT-IDENTITY
        STATUS      current
        DESCRIPTION "The authoritative identifier for a
                    power supply bay in an Aruba 8400 switch
                    chassis. "
        ::= { wndSlots 2 }

arubaWiredSwitch8400ManagementModuleSlot OBJECT-IDENTITY
        STATUS      current
        DESCRIPTION "The authoritative identifier for a
                    Management Module bay in a Aruba 8400 switch. "
        ::= { wndSlots 3 }

arubaWiredSwitch8400LineCardSlot OBJECT-IDENTITY
        STATUS      current
        DESCRIPTION "The authoritative identifier for a line card
                    module slot in an Aruba 8400 switch chassis. "
        ::= { wndSlots 4 }

arubaWiredSwitch8400FabricCardSlot OBJECT-IDENTITY
        STATUS      current
        DESCRIPTION "The authoritative identifier for a fabric
                    module slot in an Aruba 8400 switch chassis. "
        ::= { wndSlots 5 }

arubaWiredSwitch8400RearDisplayCardSlot OBJECT-IDENTITY
        STATUS      current
        DESCRIPTION "The authoritative identifier for a fabric
                    module slot in an Aruba 8400 switch chassis. "
        ::= { wndSlots 6 }

arubaWiredSwitch8320FanTraySlot OBJECT-IDENTITY
        STATUS      current
        DESCRIPTION "Represents slot for Aruba F2B Fan Tray. "
        ::= { wndSlots 7 }

arubaWiredSwitch8320PowerSupplySlot OBJECT-IDENTITY
        STATUS      current
        DESCRIPTION "The authoritative identifier for a
                    power supply bay in an Aruba 8320 switch
                    chassis. "
        ::= { wndSlots 8 }

arubaWiredSwitch8325FanTraySlot OBJECT-IDENTITY
        STATUS      current
        DESCRIPTION "Represents slot for Aruba Fan Tray. "
        ::= { wndSlots 9 }

arubaWiredSwitch8325PowerSupplySlot OBJECT-IDENTITY
        STATUS      current
        DESCRIPTION "The authoritative identifier for a
                    power supply bay in an Aruba 8325 switch
                    chassis. "
        ::= { wndSlots 10 }

arubaWiredSwitch6300FanTraySlot OBJECT-IDENTITY
        STATUS      current
        DESCRIPTION "Represents slot for Aruba 6300M Switch Fan Tray. "
        ::= { wndSlots 11 }

arubaWiredSwitch6300PowerSupplySlot OBJECT-IDENTITY
        STATUS      current
        DESCRIPTION "The authoritative identifier for a
                    power supply bay in an Aruba 6300M switch.  "
        ::= { wndSlots 12 }

arubaWiredSwitch6400ManagementModuleSlot OBJECT-IDENTITY
        STATUS      current
        DESCRIPTION "The authoritative identifier for a
                    Management Module slot in a Aruba 6400 switch. "
        ::= { wndSlots 13 }

arubaWiredSwitch6400LineCardSlot OBJECT-IDENTITY
        STATUS      current
        DESCRIPTION "The authoritative identifier for a line card
                    module slot in an Aruba 6400 switch chassis. "
        ::= { wndSlots 14 }

arubaWiredSwitch6400FanTraySlot OBJECT-IDENTITY
        STATUS      current
        DESCRIPTION "Represents slot for Aruba 6400 Fan Tray. "
        ::= { wndSlots 15 }

arubaWiredSwitch6400PowerSupplySlot OBJECT-IDENTITY
        STATUS      current
        DESCRIPTION "The authoritative identifier for a
                    power supply slot in an Aruba 6400 switch
                    chassis. "
        ::= { wndSlots 16 }

arubaWiredSwitch8360FanTraySlot OBJECT-IDENTITY
        STATUS      current
        DESCRIPTION "Represents slot for Aruba 8360 Fan Tray. "
        ::= { wndSlots 17 }

arubaWiredSwitch8360PowerSupplySlot OBJECT-IDENTITY
        STATUS      current
        DESCRIPTION "The authoritative identifier for a
                    power supply slot in an Aruba 8360 switch. "
        ::= { wndSlots 18 }

-- modules are sub types of parts

wndModules  OBJECT IDENTIFIER ::= { wndComponentIds 3 }

arubaWiredSwitchManagementModuleJL368A OBJECT-IDENTITY
        STATUS      current
        DESCRIPTION "The authoritative identifier for Aruba 8400 Management Module. "
        ::= { wndModules 1 }

arubaWiredSwitchModuleJL363A OBJECT-IDENTITY
        STATUS      current
        DESCRIPTION "The authoritative identifier for Aruba 8400X 32-port 10GbE SFP/SFP+ with MACsec Advanced Module. "
        ::= { wndModules 2 }

arubaWiredSwitchModuleJL365A OBJECT-IDENTITY
        STATUS      current
        DESCRIPTION "The authoritative identifier for Aruba 8400X 8-port 40GbE QSFP+ Advanced Module."
        ::= { wndModules 3 }

arubaWiredSwitchModuleJL366A OBJECT-IDENTITY
        STATUS      current
        DESCRIPTION "The authoritative identifier for Aruba 8400X 6-port 40GbE/100GbE QSFP28 Advanced Module. "
        ::= { wndModules 4 }

arubaWiredSwitchFabricModuleJL367A OBJECT-IDENTITY
        STATUS      current
        DESCRIPTION "The authoritative identifier for Aruba 8400X 7.2Tbps Fabric Module. "
        ::= { wndModules 5 }

arubaWiredSwitchFanModuleJL370A OBJECT-IDENTITY
        STATUS      current
        DESCRIPTION "The authoritative identifier for Aruba 8400 Fan for X731 Fan Tray. "
        ::= { wndModules 6 }

arubaWiredSwitchPowerSupplyUnitJL372A OBJECT-IDENTITY
        STATUS      current
        DESCRIPTION "The authoritative identifier for Aruba X382 54VDC 2700W AC Power Supply. "
        ::= { wndModules 7 }

arubaWiredSwitchJL369AFanTray OBJECT-IDENTITY
        STATUS      current
        DESCRIPTION "The authoritative identifier for Aruba X731 Fan Tray. "
        ::= { wndModules 8 }

arubaWiredSwitchModuleJL479A OBJECT-IDENTITY
        STATUS      current
        DESCRIPTION "The authoritative identifier for Aruba 8320 48p 10G SFP/SFP+ and 6p 40G QSFP+ Advanced Module."
        ::= { wndModules 9 }

arubaWiredSwitchPowerSupplyUnitJL480A OBJECT-IDENTITY
        STATUS      current
        DESCRIPTION "The authoritative identifier for Aruba 8320 400W AC Power Supply. "
        ::= { wndModules 10 }

arubaWiredSwitchJL481AFanTray OBJECT-IDENTITY
        STATUS      current
        DESCRIPTION "The authoritative identifier for Aruba 8320 Fan Tray. "
        ::= { wndModules 11 }

arubaWiredSwitchRearDisplayModule8400 OBJECT-IDENTITY
        STATUS      current
        DESCRIPTION "The authoritative identifier for Aruba 8400 Rear Display Module. "
        ::= { wndModules 12 }

arubaWiredSwitch1GbMaxPort OBJECT-IDENTITY
        STATUS      current
        DESCRIPTION "The authoritative identifier for a 1Gb maximum speed port."
        ::= { wndModules 13 }

arubaWiredSwitch10GbMaxPort OBJECT-IDENTITY
        STATUS      current
        DESCRIPTION "The authoritative identifier for a 10Gb maximum speed port."
        ::= { wndModules 14 }

arubaWiredSwitch25GbMaxPort OBJECT-IDENTITY
        STATUS      current
        DESCRIPTION "The authoritative identifier for a 25Gb maximum speed port."
        ::= { wndModules 15 }

arubaWiredSwitch40GbMaxPort OBJECT-IDENTITY
        STATUS      current
        DESCRIPTION "The authoritative identifier for a 40Gb maximum speed port."
        ::= { wndModules 16 }

arubaWiredSwitch100GbMaxPort OBJECT-IDENTITY
        STATUS      current
        DESCRIPTION "The authoritative identifier for a 100Gb maximum speed port."
        ::= { wndModules 17 }

arubaWiredSwitchSmartRatePort OBJECT-IDENTITY
        STATUS      current
        DESCRIPTION "The authoritative identifier for a Smart Rate multi-gigabit port."
        ::= { wndModules 18 }

arubaWiredSwitchModuleJL579A OBJECT-IDENTITY
        STATUS      current
        DESCRIPTION "The authoritative identifier for Aruba 8320 32p 40GbE QSFP+ Advanced Module."
        ::= { wndModules 19 }

arubaWiredSwitchModuleJL581A OBJECT-IDENTITY
        STATUS      current
        DESCRIPTION "The authoritative identifier for Aruba 8320 48p 1G/10GBASE-T and 6p 40G QSFP+ Advanced Module."
        ::= { wndModules 20 }

arubaWiredSwitchModuleJL635A OBJECT-IDENTITY
        STATUS      current
        DESCRIPTION "The authoritative identifier for Aruba 8325-48Y8C Module."
        ::= { wndModules 21 }

arubaWiredSwitchModuleJL624A OBJECT-IDENTITY
        STATUS      current
        DESCRIPTION "The authoritative identifier for Aruba 8325-48Y8C FB Module."
        ::= { wndModules 22 }

arubaWiredSwitchModuleJL625A OBJECT-IDENTITY
        STATUS      current
        DESCRIPTION "The authoritative identifier for Aruba 8325-48Y8C BF Module."
        ::= { wndModules 23 }

arubaWiredSwitchModuleJL636A OBJECT-IDENTITY
        STATUS      current
        DESCRIPTION "The authoritative identifier for Aruba 8325-32C Module."
        ::= { wndModules 24 }

arubaWiredSwitchModuleJL626A OBJECT-IDENTITY
        STATUS      current
        DESCRIPTION "The authoritative identifier for Aruba 8325-32C FB Module."
        ::= { wndModules 25 }

arubaWiredSwitchModuleJL627A OBJECT-IDENTITY
        STATUS      current
        DESCRIPTION "The authoritative identifier for Aruba 8325-32C BF Module."
        ::= { wndModules 26 }

arubaWiredSwitchPowerSupplyUnitJL632A OBJECT-IDENTITY
        STATUS      current
        DESCRIPTION "The authoritative identifier for Aruba 8325 650W 100-240V FB AC Power Supply. "
        ::= { wndModules 27 }

arubaWiredSwitchPowerSupplyUnitJL633A OBJECT-IDENTITY
        STATUS      current
        DESCRIPTION "The authoritative identifier for Aruba 8325 650W 100-240V BF AC Power Supply. "
        ::= { wndModules 28 }

arubaWiredSwitchFanTrayJL628A OBJECT-IDENTITY
        STATUS      current
        DESCRIPTION "The authoritative identifier for Aruba 8325-48Y8C F2B Fan Tray. "
        ::= { wndModules 29 }

arubaWiredSwitchFanTrayJL629A OBJECT-IDENTITY
        STATUS      current
        DESCRIPTION "The authoritative identifier for Aruba 8325-48Y8C B2F Fan Tray. "
        ::= { wndModules 30 }

arubaWiredSwitchFanTrayJL630A OBJECT-IDENTITY
        STATUS      current
        DESCRIPTION "The authoritative identifier for Aruba 8325-32C F2B Fan Tray. "
        ::= { wndModules 31 }

arubaWiredSwitchFanTrayJL631A OBJECT-IDENTITY
        STATUS      current
        DESCRIPTION "The authoritative identifier for Aruba 8325-32C B2F Fan Tray. "
        ::= { wndModules 32 }

arubaWiredSwitchModuleJL658A OBJECT-IDENTITY
        STATUS      current
        DESCRIPTION "The authoritative identifier for Aruba 6300M 24SFP+ 4SFP56 Advanced Module."
        ::= { wndModules 33 }

arubaWiredSwitchModuleJL659A OBJECT-IDENTITY
        STATUS      current
        DESCRIPTION "The authoritative identifier for Aruba 6300M 48SR5 CL6 PoE 4SFP56 Advanced Module."
        ::= { wndModules 34 }

arubaWiredSwitchModuleJL660A OBJECT-IDENTITY
        STATUS      current
        DESCRIPTION "The authoritative identifier for Aruba 6300M 24SR5 CL6 PoE 4SFP56 Advanced Module."
       ::= { wndModules 35 }

arubaWiredSwitchModuleJL661A OBJECT-IDENTITY
        STATUS      current
        DESCRIPTION "The authoritative identifier for Aruba 6300M 48G CL4 PoE 4SFP56 Advanced Module."
       ::= { wndModules 36 }

arubaWiredSwitchModuleJL662A OBJECT-IDENTITY
        STATUS      current
        DESCRIPTION "The authoritative identifier for Aruba 6300M 24G CL4 PoE 4SFP56 Advanced Module."
       ::= { wndModules 37 }

arubaWiredSwitchModuleJL663A OBJECT-IDENTITY
        STATUS      current
        DESCRIPTION "The authoritative identifier for Aruba 6300M 48G 4SFP56 Advanced Module."
       ::= { wndModules 38 }

arubaWiredSwitchModuleJL664A OBJECT-IDENTITY
        STATUS      current
        DESCRIPTION "The authoritative identifier for Aruba 6300M 24G 4SFP56 Advanced Module."
       ::= { wndModules 39 }

arubaWiredSwitchModuleJL665A OBJECT-IDENTITY
        STATUS      current
        DESCRIPTION "The authoritative identifier for Aruba 6300F 48G CL4 PoE 4SFP56 Advanced Module."
       ::= { wndModules 40 }

arubaWiredSwitchModuleJL666A OBJECT-IDENTITY
        STATUS      current
        DESCRIPTION "The authoritative identifier for Aruba 6300F 24G CL4 PoE 4SFP56 Advanced Module."
       ::= { wndModules 41 }

arubaWiredSwitchModuleJL667A OBJECT-IDENTITY
        STATUS      current
        DESCRIPTION "The authoritative identifier for Aruba 6300F 48G 4SFP56 Advanced Module."
       ::= { wndModules 42 }

arubaWiredSwitchModuleJL668A OBJECT-IDENTITY
        STATUS      current
        DESCRIPTION "The authoritative identifier for Aruba 6300F 24G 4SFP56 Advanced Module."
       ::= { wndModules 43 }

arubaWiredSwitchFanTrayJL669A OBJECT-IDENTITY
        STATUS      current
        DESCRIPTION "The authoritative identifier for Aruba 6300 Fan Tray. "
        ::= { wndModules 44 }

arubaWiredSwitchPowerSupplyUnitJL085A OBJECT-IDENTITY
        STATUS      current
        DESCRIPTION "The authoritative identifier for Aruba X371 12VDC 250W100-240VAC Power Supply. "
        ::= { wndModules 45 }

arubaWiredSwitchPowerSupplyUnitJL086A OBJECT-IDENTITY
        STATUS      current
        DESCRIPTION "The authoritative identifier for Aruba X372 54VDC 680W 100-240VAC Power Supply. "
        ::= { wndModules 46 }

arubaWiredSwitchPowerSupplyUnitJL087A OBJECT-IDENTITY
        STATUS      current
        DESCRIPTION "The authoritative identifier for Aruba X372 54VDC 1050W 110-240VAC Power Supply. "
        ::= { wndModules 47 }

arubaWiredSwitchPowerSupplyUnitJL670A OBJECT-IDENTITY
        STATUS      current
        DESCRIPTION "The authoritative identifier for Aruba X372 54VDC 1600W 110-240VAC Power Supply. "
        ::= { wndModules 48 }

arubaWiredSwitchModuleJL687A OBJECT-IDENTITY
        STATUS      current
        DESCRIPTION "The authoritative identifier for Aruba 8400X-32Y 32p 1/10/25G SFP/SFP+/SFP28 Module. "
        ::= { wndModules 350 }

arubaWiredSwitch50GbMaxPort OBJECT-IDENTITY
        STATUS      current
        DESCRIPTION "The authoritative identifier for a 50Gb maximum speed port."
        ::= { wndModules 50 }

arubaWiredSwitchR0X31A OBJECT-IDENTITY
        STATUS      current
        DESCRIPTION "The authoritative identifier for the
                     Aruba 6400 Management Module."
        ::= { wndModules 51 }

arubaWiredSwitchR0X32A OBJECT-IDENTITY
        STATUS      current
        DESCRIPTION "The authoritative identifier for the
                     Aruba 6400 Fan Tray."
        ::= { wndModules 52 }

arubaWiredSwitchR0X33A OBJECT-IDENTITY
        STATUS      current
        DESCRIPTION "The authoritative identifier for the
                     Aruba 6400 C16 Inlet Adapter."
        ::= { wndModules 53 }

arubaWiredSwitchR0X34A OBJECT-IDENTITY
        STATUS      current
        DESCRIPTION "The authoritative identifier for the
                     Aruba 6400 C20 Inlet Adapter."
        ::= { wndModules 54 }

arubaWiredSwitchR0X35A OBJECT-IDENTITY
        STATUS      current
        DESCRIPTION "The authoritative identifier for the
                     Aruba 6400 1800W Power Supply with C16 Inlet Adapter."
        ::= { wndModules 55 }

arubaWiredSwitchR0X36A OBJECT-IDENTITY
        STATUS      current
        DESCRIPTION "The authoritative identifier for the
                     Aruba 6400 3000W Power Supply with C20 Inlet Adapter."
        ::= { wndModules 56 }

arubaWiredSwitchR0X37A OBJECT-IDENTITY
        STATUS      current
        DESCRIPTION "The authoritative identifier for the
                     Aruba 6400 4-post Rack Mount Kit."
        ::= { wndModules 57 }

arubaWiredSwitchR0X38A OBJECT-IDENTITY
        STATUS      current
        DESCRIPTION "The authoritative identifier for the
                     Aruba 6400 48-port 1GbE PoE Class 4 Module."
        ::= { wndModules 58 }

arubaWiredSwitchR0X39A OBJECT-IDENTITY
        STATUS      current
        DESCRIPTION "The authoritative identifier for the
                     Aruba 6400 48-port 1GbE PoE Class 4 and 4-port SFP56 Module."
        ::= { wndModules 59 }

arubaWiredSwitchR0X40A OBJECT-IDENTITY
        STATUS      current
        DESCRIPTION "The authoritative identifier for the
                     Aruba 6400 48-port 1GbE PoE Class 6 and 4-port SFP56 Module."
        ::= { wndModules 60 }

arubaWiredSwitchR0X41A OBJECT-IDENTITY
        STATUS      current
        DESCRIPTION "The authoritative identifier for the
                     Aruba 6400 48-port HPE Smart Rate PoE Class 6 and 4-port SFP56 Module."
        ::= { wndModules 61 }

arubaWiredSwitchR0X42A OBJECT-IDENTITY
        STATUS      current
        DESCRIPTION "The authoritative identifier for the
                     Aruba 6400 24-port HPE Smart Rate and 4-port SFP56 Module."
        ::= { wndModules 62 }

arubaWiredSwitchR0X43A OBJECT-IDENTITY
        STATUS      current
        DESCRIPTION "The authoritative identifier for the
                     Aruba 6400 24-port SFP+ and 4-port SFP56 Module."
        ::= { wndModules 63 }

arubaWiredSwitchR0X44A OBJECT-IDENTITY
        STATUS      current
        DESCRIPTION "The authoritative identifier for the
                     Aruba 6400 48-port 10/25GbE SFP28 Module."
        ::= { wndModules 64 }

arubaWiredSwitchR0X45A OBJECT-IDENTITY
        STATUS      current
        DESCRIPTION "The authoritative identifier for the
                     Aruba 6400 12-Port 40/100GbE QSFP28 Module."
        ::= { wndModules 65 }

arubaWiredSwitchModuleJL762A OBJECT-IDENTITY
        STATUS      current
        DESCRIPTION "The authoritative identifier for Aruba 6300M 48G 4SFP56 Pwr2Prt Advanced Module."
       ::= { wndModules 70 }

arubaWiredSwitchFanTrayJL761A OBJECT-IDENTITY
        STATUS      current
        DESCRIPTION "The authoritative identifier for Aruba 6300M Pwr2Prt Fan Tray. "
        ::= { wndModules 71 }

arubaWiredSwitchPowerSupplyUnitJL760A OBJECT-IDENTITY
        STATUS      current
        DESCRIPTION "The authoritative identifier for Aruba X371 12VDC 250W 100-240VAC Power-to-Ports Power Supply."
        ::= { wndModules 72 }

arubaWiredSwitchModuleJL724A OBJECT-IDENTITY
        STATUS      current
        DESCRIPTION "The authoritative identifier for Aruba 6200F 24G 4SFP+ Module."
       ::= { wndModules 90 }

arubaWiredSwitchModuleJL725A OBJECT-IDENTITY
        STATUS      current
        DESCRIPTION "The authoritative identifier for Aruba 6200F 24G CL4 4SFP+370W Module."
       ::= { wndModules 91 }

arubaWiredSwitchModuleJL726A OBJECT-IDENTITY
        STATUS      current
        DESCRIPTION "The authoritative identifier for Aruba 6200F 48G 4SFP+ Module."
       ::= { wndModules 92 }

arubaWiredSwitchModuleJL727A OBJECT-IDENTITY
        STATUS      current
        DESCRIPTION "The authoritative identifier for Aruba 6200F 48G CL4 4SFP+370W Module."
       ::= { wndModules 93 }

arubaWiredSwitchModuleJL728A OBJECT-IDENTITY
        STATUS      current
        DESCRIPTION "The authoritative identifier for Aruba 6200F 48G CL4 4SFP+740W Module."
       ::= { wndModules 94 }

arubaWiredSwitchR0X38B OBJECT-IDENTITY
        STATUS      current
        DESCRIPTION "The authoritative identifier for the
                     Aruba 6400 48-port 1GbE PoE Class 4 Module."
        ::= { wndModules 103 }

arubaWiredSwitchR0X39B OBJECT-IDENTITY
        STATUS      current
        DESCRIPTION "The authoritative identifier for the
                     Aruba 6400 48-port 1GbE PoE Class 4 and 4-port SFP56 Module."
        ::= { wndModules 104 }

arubaWiredSwitchR0X40B OBJECT-IDENTITY
        STATUS      current
        DESCRIPTION "The authoritative identifier for the
                     Aruba 6400 48-port 1GbE PoE Class 6 and 4-port SFP56 Module."
        ::= { wndModules 105 }

arubaWiredSwitchModuleJL675A OBJECT-IDENTITY
        STATUS      current
        DESCRIPTION "The authoritative identifier for the Aruba 6100 48G CLS4 4SFP+ 370W Module."
       ::= { wndModules 106 }

arubaWiredSwitchModuleJL676A OBJECT-IDENTITY
        STATUS      current
        DESCRIPTION "The authoritative identifier for the Aruba 6100 48G 4SFP+ Module."
       ::= { wndModules 107 }

arubaWiredSwitchModuleJL677A OBJECT-IDENTITY
        STATUS      current
        DESCRIPTION "The authoritative identifier for the Aruba 6100 24G CLS4 4SFP+ 370W Module."
       ::= { wndModules 108 }

arubaWiredSwitchModuleJL678A OBJECT-IDENTITY
        STATUS      current
        DESCRIPTION "The authoritative identifier for the Aruba 6100 24G 4SFP+ Module."
       ::= { wndModules 109 }

arubaWiredSwitchModuleJL679A OBJECT-IDENTITY
        STATUS      current
        DESCRIPTION "The authoritative identifier for the Aruba 6100 12G CLS4 2G/2SFP+ 139W Module."
       ::= { wndModules 110 }

arubaWiredSwitchNonPoEPowerSupplyUnit OBJECT-IDENTITY
        STATUS      current
        DESCRIPTION "The authoritative identifier for Aruba 12VDC and 200W Power Supply. "
        ::= { wndModules 111 }

arubaWiredSwitchPoEPowerSupplyUnit OBJECT-IDENTITY
        STATUS      current
        DESCRIPTION "The authoritative identifier for Aruba 12VDC and 54VDC 950W Power Supply. "
        ::= { wndModules 112 }

arubaWiredSwitchModuleJL717A OBJECT-IDENTITY
        STATUS      current
        DESCRIPTION "The authoritative identifier for the Aruba 8360
        32p 1/10/25G SFP/SFP+/SFP28 and 4p 40/100G QSFP+/QSFP28 advanced module."
        ::= { wndModules 113 }

arubaWiredSwitchModuleJL718A OBJECT-IDENTITY
        STATUS      current
        DESCRIPTION "The authoritative identifier for the Aruba 8360
        16p 1/10/25G SFP/SFP+/SFP28 and 2p 40/100G QSFP+/QSFP28 advanced module."
        ::= { wndModules 114 }

arubaWiredSwitchModuleJL719A OBJECT-IDENTITY
        STATUS      current
        DESCRIPTION "The authoritative identifier for the Aruba 8360
        48p 1/10/25G SFP/SFP+/SFP28 and 6p 40/100G QSFP+/QSFP28 advanced module."
        ::= { wndModules 115 }

arubaWiredSwitchModuleJL720A OBJECT-IDENTITY
        STATUS      current
        DESCRIPTION "The authoritative identifier for the Aruba 8360
        48p 1/10G BASE-T and 4p 40/100G QSFP+/QSFP28 advanced module."
        ::= { wndModules 116 }

arubaWiredSwitchModuleJL721A OBJECT-IDENTITY
        STATUS      current
        DESCRIPTION "The authoritative identifier for the Aruba 8360
        12p 40/100G QSFP+/QSFP28 advanced module."
        ::= { wndModules 117 }

arubaWiredSwitchModuleJL722A OBJECT-IDENTITY
        STATUS      current
        DESCRIPTION "The authoritative identifier for the Aruba 8360
        48p 1/10G SFP/SFP+ and 2p 40/100G QSFP+/QSFP28 advanced module."
        ::= { wndModules 118 }

arubaWiredSwitchPowerSupplyUnitJL600A OBJECT-IDENTITY
        STATUS      current
        DESCRIPTION "The authoritative identifier for the Aruba 550W 12V F2B Power Supply. "
        ::= { wndModules 119 }

arubaWiredSwitchPowerSupplyUnitJL601A OBJECT-IDENTITY
        STATUS      current
        DESCRIPTION "The authoritative identifier for the Aruba 850W 12V F2B Power Supply. "
        ::= { wndModules 120 }

arubaWiredSwitchPowerSupplyUnitJL712A OBJECT-IDENTITY
        STATUS      current
        DESCRIPTION "The authoritative identifier for the Aruba 550W 12V B2F Power Supply. "
        ::= { wndModules 121 }

arubaWiredSwitchPowerSupplyUnitJL713A OBJECT-IDENTITY
        STATUS      current
        DESCRIPTION "The authoritative identifier for the Aruba 850W 12V B2F Power Supply. "
        ::= { wndModules 122 }

arubaWiredSwitchFanTrayJL714A OBJECT-IDENTITY
        STATUS      current
        DESCRIPTION "The authoritative identifier for Aruba 8360 F2B Fan Tray. "
        ::= { wndModules 123 }

arubaWiredSwitchFanTrayJL715A OBJECT-IDENTITY
        STATUS      current
        DESCRIPTION "The authoritative identifier for Aruba 8360 B2F Fan Tray. "
        ::= { wndModules 124 }

arubaWiredSwitch36WPowerSupplyUnit OBJECT-IDENTITY
        STATUS      current
        DESCRIPTION "The authoritative identifier for Aruba 12VDC and 36W Power Supply. "
        ::= { wndModules 125 }

arubaWiredSwitch65WPowerSupplyUnit OBJECT-IDENTITY
        STATUS      current
        DESCRIPTION "The authoritative identifier for Aruba 12VDC and 65W Power Supply. "
        ::= { wndModules 126 }

arubaWiredSwitch165WPowerSupplyUnit OBJECT-IDENTITY
        STATUS      current
        DESCRIPTION "The authoritative identifier for Aruba 12VDC and 165W Power Supply. "
        ::= { wndModules 127 }

arubaWiredSwitch500WPowerSupplyUnit OBJECT-IDENTITY
        STATUS      current
        DESCRIPTION "The authoritative identifier for Aruba 12VDC and 500W Power Supply. "
        ::= { wndModules 128 }

arubaWiredSwitch300WPowerSupplyUnit OBJECT-IDENTITY
        STATUS      current
        DESCRIPTION "The authoritative identifier for Aruba 54VDC 300W Power Supply. "
        ::= { wndModules 131 }

arubaWiredSwitchExternalPowerSupplyUnit OBJECT-IDENTITY
        STATUS      current
        DESCRIPTION "The authoritative identifier for generic External Power Supply. "
        ::= { wndModules 132 }

-- Feature Sub-tree where we allocate OID for Proprietary MIBs

arubaWiredLoopProtectMIB     OBJECT IDENTIFIER ::= { wndFeatures 1 }

arubaWiredMclagMIB           OBJECT IDENTIFIER ::= { wndFeatures 2 }

arubaWiredMgmdSnoopingMIB    OBJECT IDENTIFIER ::= { wndFeatures 3 }

arubaWiredMgmdRmonTrapMIB    OBJECT IDENTIFIER ::= { wndFeatures 4 }

arubaWiredRpvstMIB           OBJECT IDENTIFIER ::= { wndFeatures 5 }

arubaWiredMvrpMIB            OBJECT IDENTIFIER ::= { wndFeatures 6 }

arubaWiredVsxMIB             OBJECT IDENTIFIER ::= { wndFeatures 7 }

arubaWiredPoeMIB             OBJECT IDENTIFIER ::= { wndFeatures 8 }

arubaWiredLldpMIB            OBJECT IDENTIFIER ::= { wndFeatures 9 }

arubaWiredVsfMIB             OBJECT IDENTIFIER ::= { wndFeatures 10 }

arubaWiredChassisMIB         OBJECT IDENTIFIER ::= { wndFeatures 11 }

arubaWiredCiptMIB            OBJECT IDENTIFIER ::= { wndFeatures 12 }

arubaWiredMstpMIB            OBJECT IDENTIFIER ::= { wndFeatures 13 }

arubaWiredMdnsMIB            OBJECT IDENTIFIER ::= { wndFeatures 14 }

arubaWiredVsfv2MIB           OBJECT IDENTIFIER ::= { wndFeatures 15 }

arubaWiredPortAccessMIB      OBJECT IDENTIFIER ::= { wndFeatures 17 }

arubaWiredPortVlanMIB        OBJECT IDENTIFIER ::= { wndFeatures 18 }

END
